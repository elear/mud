module ietf-mud-detext-example {
  yang-version 1.1;
  namespace "urn:ietf:params:xml:ns:yang:ietf-mud-detext-example";
  prefix ietf-mud-detext-example;

  import ietf-mud {
    prefix ietf-mud;
  }

  organization
    "IETF OPSAWG (Ops Area) Working Group";
  contact
    "WG Web: http://tools.ietf.org/wg/opsawg/
     WG List: opsawg@ietf.org
     Author: Eliot Lear
     lear@cisco.com
     Author: Ralph Droms
     rdroms@gmail.com
     Author: Dan Romascanu
     dromasca@gmail.com

    ";
  description
    "Sample extension to a MUD module to indicate a need
     for DETNET support.";

  revision 2018-01-20 {
    description
      "Initial revision.";
    reference
      "RFC XXXX: Manufacturer Usage Description
       Specification";
  }

  augment "/ietf-mud:mud" {
    description
      "This adds a simple extension for a manufacturer
        to indicate whether DETNET is required by a
       device.";
    leaf is-detnet-required {
      type boolean;
      description
        "This value will equal true if a device requires
         detnet to properly function";
    }
  }
}
